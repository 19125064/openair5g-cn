-- ASN1START
-- **************************************************************
--
-- Common definitions
--
-- **************************************************************

NGAP-CommonDataTypes {
itu-t (0) identified-organization (4) etsi (0) mobileDomain (0) 
ngran-Access (22) modules (3) ngap (1) version1 (1) ngap-CommonDataTypes (3) }

DEFINITIONS AUTOMATIC TAGS ::= 

BEGIN

Criticality		::= ENUMERATED { reject, ignore, notify }

Presence		::= ENUMERATED { optional, conditional, mandatory }

PrivateIE-ID	::= CHOICE {
	local				INTEGER (0..65535),
	global				OBJECT IDENTIFIER
}

ProcedureCode		::= INTEGER {
    id-AMFConfigurationUpdate(0),
    id-AMFStatusIndication(1),                                    
    id-CellTrafficTrace(2),                                                 
    id-DeactivateTrace(3),                                            
    id-DownlinkNASTransport(4),                         
    id-DownlinkNonUEAssociatedNRPPaTransport(5),        
    id-DownlinkRANConfigurationTransfer(6),                   
    id-DownlinkRANStatusTransfer(7),                     
    id-DownlinkUEAssociatedNRPPaTransport(8),        
    id-ErrorIndication(9),                                            
    id-HandoverCancel(10),                                         
    id-HandoverNotification(11),                                   
    id-HandoverPreparation(12),                                  
    id-HandoverResourceAllocation(13),                        
    id-InitialContextSetup(14),                                       
    id-InitialUEMessage(15),                                         
    id-LocationReportingControl(16),                    
    id-LocationReportingFailureIndication(17),        
    id-LocationReport(18),                                                
    id-NASNonDeliveryIndication(19),                                    
    id-NGReset(20),                                                                   
    id-NGSetup(21),                   
    id-OverloadStart(22),                                           
    id-OverloadStop(23),                                               
    id-Paging(24),                                                            
    id-PathSwitchRequest(25),                                       
    id-PDUSessionResourceModify(26),                                
    id-PDUSessionResourceModifyIndication(27),       
    id-PDUSessionResourceRelease(28),                
    id-PDUSessionResourceSetup(29),                         
    id-PDUSessionResourceNotify(30),                           
    id-PrivateMessage(31),                                       
    id-PWSCancel(32),                                                   
    id-PWSFailureIndication(33),                                       
    id-PWSRestartIndication(34),                                  
    id-RANConfigurationUpdate(35),                                  
    id-RerouteNASRequest(36),                                  
    id-RRCInactiveTransitionReport(37),                   
    id-TraceFailureIndication(38),                              
    id-TraceStart(39),                                           
    id-UEContextModification(40),                             
    id-UEContextRelease(41),                                            
    id-UEContextReleaseRequest(42),                                    
    id-UERadioCapabilityCheck(43),                                  
    id-UERadioCapabilityInfoIndication(44),                     
    id-UETNLABindingRelease(45),                                  
    id-UplinkNASTransport(46),                                       
    id-UplinkNonUEAssociatedNRPPaTransport(47),         
    id-UplinkRANConfigurationTransfer(48),               
    id-UplinkRANStatusTransfer(49),                         
    id-UplinkUEAssociatedNRPPaTransport(50),               
    id-WriteReplaceWarning(51)                                  
}(0..255)

ProtocolExtensionID	::= INTEGER (0..65535)

ProtocolIE-ID		::= INTEGER{
        id-AllowedNSSAI(0),                                                                         
        id-AMFName(1),                                                
        id-AMFOverloadResponsie(2),                                   
        id-AMFSetID(3),                                              
        id-AMF-TNLAssociationFailedToSetupList(4),                 
        id-AMF-TNLAssociationSetupList(5),                        
        id-AMF-TNLAssociationToAddList(6),                       
        id-AMF-TNLAssociationToRemoveList(7),                                      
        id-AMF-TNLAssociationToUpdateList(8),                                     
        id-AMFTrafficLoadReductionIndication(9),                                 
        id-AMF-UE-NGAP-ID(10),                                                  
        id-AssistanceDataForPaging(11),                                        
        id-BroadcastCancelledAreaList(12),                                    
        id-BroadcastCompletedAreaList(13),                                   
        id-CancelAllWarningMessages(14),                                    
        id-Cause(15),                                                   
        id-CellIDListForRestart(16),                                  
        id-ConcurrentWarningMessageInd(17),                          
        id-CoreNetworkAssistanceInformation(18),                    
        id-CriticalityDiagnostics(19),                                                               
        id-DataCodingScheme(20),                                                                    
        id-DefaultPagingDRX(21),                                                                   
        id-DirectForwardingPathAvailability(22),                                           
        id-EmergencyAreaIDListForRestart(23),                                            
        id-EmergencyFallbackIndicator(24),                                              
        id-EUTRA-CGI(25),                                                              
        id-FiveG-S-TMSI(26),                                                         
        id-GlobalRANNodeID(27),                                                   
        id-GUAMI(28),                                                            
        id-HandoverType(29),                                                   
        id-IMSVoiceSupportIndicator(30),                                      
        id-IndexToRFSP(31),                                                  
        id-InfoOnRecommendedCellsAndRANNodesForPaging(32),                  
        id-LocationReportingRequestType(33),                               
        id-MaskedIMEISV(34),                                              
        id-MessageIdentifier(35),                                        
        id-MobilityRestrictionList(36),                                 
        id-NASC(37),                                                                            
        id-NAS-PDU(38),                                                                   
        id-NASSecurityParametersFromNGRAN(39),                                       
        id-NewAMF-UE-NGAP-ID(40),
        id-NewSecurityContextInd(41),                                                                
        id-NGAP-Message(42),                                                                   
        id-NGRAN-CGI(43),                                                                   
        id-NGRANTraceID(44),                                                             
        id-NR-CGI(45),                                                                
        id-NRPPa-PDU(46),                                                            
        id-NumberOfBroadcastsRequested(47),                                        
        id-OldAMF(48),                                                            
        id-OverloadStartNSSAIList(49),                                           
        id-PagingDRX(50),                                                     
        id-PagingOrigin(51),                                                                
        id-PagingPriority(52),                                                                     
        id-PDUSessionResourceAdmittedList(53),                                           
        id-PDUSessionResourceFailedToModifyListModRes(54),                 
        id-PDUSessionResourceFailedToSetupListCxtRes(55),                    
        id-PDUSessionResourceFailedToSetupListHOAck(56),                            
        id-PDUSessionResourceFailedToSetupListPSReq(57),                             
        id-PDUSessionResourceFailedToSetupListSURes(58),                             
        id-PDUSessionResourceHandoverList(59),                                            
        id-PDUSessionResourceListCxtRelCpl(60),                                           
        id-PDUSessionResourceListHORqd(61),                                             
        id-PDUSessionResourceModifyListModCfm(62),                                   
        id-PDUSessionResourceModifyListModInd(63),                                  
        id-PDUSessionResourceModifyListModReq(64),                                
        id-PDUSessionResourceModifyListModRes(65),                               
        id-PDUSessionResourceNotifyList(66),                                    
        id-PDUSessionResourceReleasedListNot(67),                                    
        id-PDUSessionResourceReleasedListPSAck(68),                                  
        id-PDUSessionResourceReleasedListPSFail(69),                                
        id-PDUSessionResourceReleasedListRelRes(70),                                 
        id-PDUSessionResourceSetupListCxtReq(71),                                
        id-PDUSessionResourceSetupListCxtRes(72),                                  
        id-PDUSessionResourceSetupListHOReq(73),                                          
        id-PDUSessionResourceSetupListSUReq(74),                                      
        id-PDUSessionResourceSetupListSURes(75),                                     
        id-PDUSessionResourceToBeSwitchedDLList(76),                                
        id-PDUSessionResourceSwitchedList(77),                                   
        id-PDUSessionResourceToReleaseListHOCmd(78),                            
        id-PDUSessionResourceToReleaseListRelCmd(79),                          
        id-PLMNSupportList(80),
        id-PWSFailedCellIDList(81),                                          
        id-RANNodeName(82),                                               
        id-RANPagingPriority(83),                                        
        id-RANStatusTransfer-TransparentContainer(84),                
        id-RAN-UE-NGAP-ID(85),                                       
        id-RelativeAMFCapacity(86),                                        
        id-RepetitionPeriod(87),                                          
        id-ResetType(88),                                               
        id-RoutingID(89),                                            
        id-RRCEstablishmentCause(90),                             
        id-RRCInactiveTransitionReportRequest(91),             
        id-RRCState(92),                                                                          
        id-SecurityContext(93),                                                                  
        id-SecurityKey(94),                                                                   
        id-SerialNumber(95),                                                              
        id-ServedGUAMIList(96),                                                           
        id-SliceSupportList(97),                                                           
        id-SONConfigurationTransferDL(98),                                            
        id-SONConfigurationTransferUL(99),                                         
        id-SourceAMF-UE-NGAP-ID(100),                                                  
        id-SourceToTarget-TransparentContainer(101),                              
        id-SupportedTAList(102),                                                
        id-TAIListForPaging(103),                                              
        id-TAIListForRestart(104),                                           
        id-TargetID(105),                                                    
        id-TargetToSource-TransparentContainer(106),                      
        id-TimeToWait(107),                                           
        id-TraceActivation(108),                             
        id-TraceCollectionEntityIPAddress(109),             
        id-UEAggregateMaximumBitRate(110),                                         
        id-UE-associatedLogicalNG-connectionList(111),                         
        id-UEContextRequest(112),                                        
        id-UE-NGAP-IDs(114),                                              
        id-UEPagingIdentity(115),                                            
        id-UEPresenceInAreaOfInterestList(116),                                
        id-UERadioCapability(117),                                                
        id-UERadioCapabilityForPaging(118),                                           
        id-UESecurityCapabilities(119),                                                  
        id-UnavailableGUAMIList(120),                                                      
        id-UserLocationInformation(121),                                                     
        id-WarningAreaList(122),
        id-WarningMessageContents(123),                                                       
        id-WarningSecurityInfo(124),                                                               
        id-WarningType(125),                                                                                 
        id-AdditionalUL-NGU-UP-TNLInformation(126),          
        id-DataForwardingNotPossible(127),                    
        id-DL-NGU-UP-TNLInformation(128),                        
        id-NetworkInstance(129),                                    
        id-PDUSessionAggregateMaximumBitRate(130),                      
        id-PDUSessionResourceFailedToModifyListModCfm(131),                
        id-PDUSessionResourceFailedToSetupListCxtFail(132),                  
        id-PDUSessionResourceListCxtRelReq(133),                                      
        id-PDUSessionType(134),                                           
        id-QosFlowAddOrModifyRequestList(135),                             
        id-QosFlowSetupRequestList(136),                       
        id-QosFlowToReleaseList(137),                           
        id-SecurityIndication(138),                                    
        id-UL-NGU-UP-TNLInformation(139),                                   
        id-UL-NGU-UP-TNLModifyList(140),                                     
        id-WarningAreaCoordinates(141)
}(0..65535)

TriggeringMessage	::= ENUMERATED { initiating-message, successful-outcome, unsuccessfull-outcome }

END
-- ASN1STOP
